#*****************************************************************************
#
#  System        : 
#  Module        : 
#  Object Name   : $RCSfile$
#  Revision      : $Revision$
#  Date          : $Date$
#  Author        : $Author$
#  Created By    : Robert Heller
#  Created       : 2026-02-23 12:02:35
#  Last Modified : <261010.0834>
#
#  Description	
#
#  Notes
#
#  History
#	
#*****************************************************************************
#
#    Copyright (C) 2026  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************




import FreeCAD as App
import Part, TechDraw, Mesh, Import
from FreeCAD import Base

import os
import sys
sys.path.append(os.path.dirname(__file__))

def debug(fmt,*args):
    print(fmt % args,file=sys.stderr)

class Adafruit_91_128x32_STEAMMA(object):
    __TotalLength = 1.3*25.4
    __TotalWidth  = 0.86*25.4
    __HoleSpaceLength = 1.1*25.4
    __HoleSpaceWidth = 0.65*25.4
    __HoleDiameter = 0.1*25.4
    __ScreenLength = 1.18*25.4
    __ScreenWidth = 0.45*25.4
    __BoardThick  = 1.6
    __ScreenThick = 0.8
    def MountHole(self,ihole,Z,ZLength):
        hOrigin = Base.Vector(self.holeOrigins[ihole].x,
                              self.holeOrigins[ihole].y,
                              Z)
        return Part.makeCylinder(self.__HoleDiameter/2,ZLength,hOrigin)
    def ScreenCutout(self,Z,ZLength):
        return Part.makePlane(self.__ScreenLength,
                              self.__ScreenWidth,
                              Base.Vector(self.screenOrigin.x,
                                          self.screenOrigin.y,
                                          Z)) \
                   .extrude(Base.Vector(0,0,ZLength))
    def __init__(self,name,origin=Base.Vector(0,0,0)):
        self.name = name
        if not isinstance(origin,Base.Vector):
            raise RuntimeError("origin is not a Vector!")
        self.origin = origin
        self.board = Part.makePlane(self.__TotalLength,
                                    self.__TotalWidth,
                                    self.origin)\
                             .extrude(Base.Vector(0,0,self.__BoardThick))
        holeXOffset = (self.__TotalLength-self.__HoleSpaceLength)/2
        holeYOffset = (self.__TotalWidth-self.__HoleSpaceWidth)/2
        self.holeOrigins = list()
        for hx in range(0,2):
            holeX = holeXOffset+(hx*self.__HoleSpaceLength)
            for hy in range(0,2):
                holeY = holeYOffset+(hy*self.__HoleSpaceWidth)
                self.holeOrigins.append(self.origin.add(Base.Vector(holeX,holeY,0)))
        self.board = self.board.cut(
            self.MountHole(0,self.origin.z,self.__BoardThick)
        )
        self.board = self.board.cut(
            self.MountHole(1,self.origin.z,self.__BoardThick)
        )
        self.board = self.board.cut(
            self.MountHole(2,self.origin.z,self.__BoardThick)
        )
        self.board = self.board.cut(
            self.MountHole(3,self.origin.z,self.__BoardThick)
        )
        self.screenOrigin = self.origin.add(
            Base.Vector((self.__TotalLength-self.__ScreenLength)/2,
                        (self.__TotalWidth-self.__ScreenWidth)/2,
                        self.__BoardThick))
        self.screen = Part.makePlane(self.__ScreenLength,
                                     self.__ScreenWidth,
                                     self.screenOrigin)\
                       .extrude(Base.Vector(0,0,self.__ScreenThick))
    def show(self,doc=None):
        if doc==None:
            doc = App.activeDocument() 
        obj = doc.addObject("Part::Feature",self.name+"_board")
        obj.Shape = self.board
        obj.Label=self.name+"_board"
        obj.ViewObject.ShapeColor=(0.0,0.0,1.0)
        obj = doc.addObject("Part::Feature",self.name+"_screen")
        obj.Shape = self.screen
        obj.Label=self.name+"_screen"
        obj.ViewObject.ShapeColor=(0.0,0.0,0.0)

class Board(object):
    __Width = 118.21
    __Length = 105.51
    __HoleSpaceW = 110.49
    __HoleSpaceL = 97.79
    __HoleDiameter = 3.2
    __BoardThick = 1.6
    __Color = (0.0,1.0,0.0)
    #__STL = os.path.join(os.path.dirname(__file__),"PocketBeagleCommandStation_SMD.stl")
    @classmethod
    def BoardSize(cls):
        return (cls.__Width,cls.__Length)
    @classmethod
    def BoardThick(cls):
        return cls.__BoardThick
    @classmethod
    def MountingHoleDiameter(cls):
        return cls.__HoleDiameter
    @classmethod 
    def HoleOffsets(cls):
        hL = (cls.__Width/2)-(cls.__HoleSpaceW/2)
        hR = (cls.__Width/2)+(cls.__HoleSpaceW/2)
        hU = (cls.__Length/2)-(cls.__HoleSpaceL/2)
        hD = (cls.__Length/2)+(cls.__HoleSpaceL/2)
        return [(hL,hU), (hR,hU), (hL, hD), (hR, hD)]
    @property
    def HoleCenters(self):
        holeOffsets = Board.HoleOffsets()
        result = list()
        for hO in holeOffsets:
            hX, hY = hO
            result.append(self.origin.add(Base.Vector(hX,hY,0)))
        return result
    @classmethod
    def HoleDiameter(cls):
        return cls.__HoleDiameter    
    def __init__(self,name,origin=Base.Vector(0,0,0)):
        self.name = name
        if not isinstance(origin,Base.Vector):
            raise RuntimeError("origin is not a Vector!")
        self.origin = origin
        board = Part.makePlane(self.__Width,self.__Length,self.origin)\
                .extrude(Base.Vector(0,0,self.__BoardThick))
        for hO in self.HoleCenters:
            hole = Part.makeCylinder(self.__HoleDiameter/2,self.__BoardThick,hO)
            board = board.cut(hole)
        self.board = board
        #board3d = Mesh.read(self.__STL)
        #board3d.translate(self.origin.x,self.origin.y,self.origin.z)
        #self.board3d = board3d
        
    def show(self,doc=None):
        if doc==None:
            doc = App.activeDocument()
        obj = doc.addObject("Part::Feature",self.name)
        obj.Shape = self.board
        obj.Label=self.name
        obj.ViewObject.ShapeColor=self.__Color
    #def show3D(self,doc=None):
    #    if doc==None:
    #        doc = App.activeDocument()
    #    obj = doc.addObject("Mesh::Feature",self.name+"_3D")
    #    obj.Mesh = self.board3d
    #    obj.Label = self.name+"_3D"

class Case(object):
    __BoardSize = Board.BoardSize()
    __BoardThick = Board.BoardThick()
    __BoardMHoleDiameter = Board.MountingHoleDiameter()
    __WallThick = 2.54
    __SpaceUnderBoard = 5.08
    __SpaceAboveBoard = 27.4-2.14
    __MountTabWidth = .375*25.4
    __MountTabLength = .5*25.4
    __MountTabHoleDiameter = 3.2
    __VentHoleDiameter = 3.5
    __PostDiameter = 6.4
    __PostHoleDiameter = Board.HoleDiameter()
    __PostShoulderDiameter = 8
    __PostShoulderDepth = 2.52
    __PostShoulderInnerDiameter = 6
    __TopPostDrillDiameter = 2.18
    __BJHeight = 10.7
    __BJWidth = 9.0932
    __BJXOffset = 52.4256
    __USBAWidth = 15.672
    __USBAHeight = 8.075
    __USBAYOffset = 63.5
    __LCCPOutXOffset = 12.25
    __LCCPInXOffset = 58.55
    __LCCPowerPlugWidth = 6
    __LCCPowerPlugHeight = 5.5
    __LCCRJ45XOffset = 21.8186
    __LCCRJ45Width = 32.6402
    __LCCRJ45Height = 12.7
    __TrackPowerXOffset = 90.8304
    __TrackPowerWidth = 15.8242
    __TrackPowerHeight = 8
    __LCCTxAct = (154.2542-85.09, 105.51-(162.0775-58.42))
    __LCCRxAct = (156.0322-85.09, 105.51-(162.0775-58.42))
    __OPSBAct  = (172.1104-85.09, 105.51-(162.0519-58.42))
    __OPSAAct  = (173.8376-85.09, 105.51-(162.0773-58.42))
    __ProgBAct = (193.1670-85.09, 105.51-(162.1430-58.42))
    __ProgAAct = (194.9196-85.09, 105.51-(162.1175-58.42))
    __Power    = (123.2154-85.09, 105.51-( 59.4614-58.42))
    __LEDZOffset = 0.7
    __LEDRodDiameter = 1.6 # AR-2 1/16" 1.6mm
    __FANXOffset = 76.781
    __FANYOffset = 41.1448
    __FANWidth =  25
    __FANHeight = 25
    __DisplayXOffset = 18
    __DisplayYOffset = 40
    @property
    def PostShoulderLength(self):
        return self.__WallThick+2.52
    @property
    def PostLength(self):
        return self.CaseBottomHeight-self.__BoardThick
    @property
    def TopPostLength(self): 
        return self.CaseTopHeight-self.__WallThick
    @property
    def TopPostDrillDepth(self):
        return self.__SpaceAboveBoard
    @property
    def CaseWidth(self):
        w,l = self.__BoardSize
        return w+(self.__WallThick*2)
    @property
    def CaseLength(self):
        w,l = self.__BoardSize
        return l+(self.__WallThick*2)
    @property
    def MountTabCY1(self):
        return self.CaseLength*.25
    @property
    def MountTabCY2(self):
        return self.CaseLength*.75
    @property
    def CaseBottomHeight(self):
        return self.__WallThick+self.__SpaceUnderBoard+self.__BoardThick
    @classmethod
    def ZOffset(cls):
        return (cls.__WallThick+cls.__SpaceUnderBoard+cls.__BoardThick)-2.33
    @property
    def CaseTopHeight(self):
        return self.__WallThick+self.__SpaceAboveBoard+(self.__WallThick/2)
    def __bottom(self):
        bot = Part.makePlane(self.CaseWidth,self.CaseLength,self.origin) \
            .extrude(Base.Vector(0,0,self.__WallThick))
        bot = bot.fuse(
            Part.makePlane(self.CaseBottomHeight,self.CaseLength,
                           self.origin.add(Base.Vector(0,self.CaseLength,0)),
                           Base.Vector(1,0,0)).extrude(Base.Vector(self.__WallThick,0,0))
        )
        bot = bot.fuse(
            Part.makePlane(self.CaseBottomHeight,self.CaseLength,
                           self.origin.add(Base.Vector(self.CaseWidth-self.__WallThick,
                                                       self.CaseLength,0)),
                           Base.Vector(1,0,0)).extrude(Base.Vector(self.__WallThick,0,0))
        )
        bot = bot.fuse(
            Part.makePlane(self.CaseBottomHeight,self.CaseWidth,
                           self.origin,
                           Base.Vector(0,1,0)).extrude(Base.Vector(0,self.__WallThick,0))
        )
        bot = bot.fuse(
            Part.makePlane(self.CaseBottomHeight,self.CaseWidth,
                           self.origin.add(Base.Vector(0,self.CaseLength-self.__WallThick,0)),
                           Base.Vector(0,1,0)).extrude(Base.Vector(0,self.__WallThick,0))
        )
        temp = Part.makePlane(self.__WallThick,self.__WallThick,self.origin,
                              Base.Vector(0,1,0))\
                .extrude(Base.Vector(0,self.CaseLength,0))
        offset = Base.Vector(self.__WallThick,0,self.__WallThick)
        rod = Part.makeCylinder(self.__WallThick,self.CaseLength,
                                self.origin.add(offset),Base.Vector(0,1,0))
        bot = bot.cut(temp.cut(rod))
        temp = Part.makePlane(self.__WallThick,self.__WallThick,
                              self.origin.add(Base.Vector(self.CaseWidth-self.__WallThick,0,0)),
                              Base.Vector(0,1,0))\
                .extrude(Base.Vector(0,self.CaseLength,0))
        offset = Base.Vector(self.CaseWidth-self.__WallThick,0,self.__WallThick)
        rod = Part.makeCylinder(self.__WallThick,self.CaseLength,
                                self.origin.add(offset),Base.Vector(0,1,0))
        bot = bot.cut(temp.cut(rod))
        temp = Part.makePlane(self.__WallThick,self.__WallThick,
                              self.origin.add(Base.Vector(0,self.__WallThick,0)),
                              Base.Vector(1,0,0)).extrude(Base.Vector(self.CaseWidth,0,0))
        offset = Base.Vector(0,self.__WallThick,self.__WallThick)
        rod = Part.makeCylinder(self.__WallThick,self.CaseWidth,
                                self.origin.add(offset),Base.Vector(1,0,0))
        bot = bot.cut(temp.cut(rod))
        temp = Part.makePlane(self.__WallThick,self.__WallThick,
                              self.origin.add(Base.Vector(0,self.CaseLength,0)),
                              Base.Vector(1,0,0)).extrude(Base.Vector(self.CaseWidth,0,0))
        offset = Base.Vector(0,self.CaseLength-self.__WallThick,self.__WallThick)
        rod = Part.makeCylinder(self.__WallThick,self.CaseWidth,
                                self.origin.add(offset),Base.Vector(1,0,0))
        bot = bot.cut(temp.cut(rod))
        temp = Part.makePlane(self.__WallThick,self.__WallThick,
                              self.origin).extrude(Base.Vector(0,0,self.CaseBottomHeight))
        rod = Part.makeCylinder(self.__WallThick,self.CaseBottomHeight,
                                self.origin.add(Base.Vector(self.__WallThick,self.__WallThick,0)))
        #self.t = temp
        #self.r = rod
        bot = bot.cut(temp.cut(rod))
        temp = Part.makePlane(self.__WallThick,self.__WallThick,
                              self.origin.add(Base.Vector(0,self.CaseLength-self.__WallThick,0))
                              ).extrude(Base.Vector(0,0,self.CaseBottomHeight))
        rod = Part.makeCylinder(self.__WallThick,self.CaseBottomHeight,
                                self.origin.add(Base.Vector(self.__WallThick,
                                                            self.CaseLength-self.__WallThick,0)))
        #self.t = temp
        #self.r = rod
        bot = bot.cut(temp.cut(rod))
        temp = Part.makePlane(self.__WallThick,self.__WallThick,
                              self.origin.add(Base.Vector(self.CaseWidth-self.__WallThick,0,0))
                              ).extrude(Base.Vector(0,0,self.CaseBottomHeight))
        rod = Part.makeCylinder(self.__WallThick,self.CaseBottomHeight,
                                self.origin.add(Base.Vector(self.CaseWidth-self.__WallThick,self.__WallThick,0)))
        #self.t = temp
        #self.r = rod
        bot = bot.cut(temp.cut(rod))
        temp = Part.makePlane(self.__WallThick,self.__WallThick,
                              self.origin.add(Base.Vector(self.CaseWidth-self.__WallThick,
                                                          self.CaseLength-self.__WallThick,0))
                              ).extrude(Base.Vector(0,0,self.CaseBottomHeight))
        rod = Part.makeCylinder(self.__WallThick,self.CaseBottomHeight,
                                self.origin.add(Base.Vector(self.CaseWidth-self.__WallThick,
                                                            self.CaseLength-self.__WallThick,0)))
        #self.t = temp
        #self.r = rod
        bot = bot.cut(temp.cut(rod))

        taborigin = self.origin.add(Base.Vector(-self.__MountTabLength,
                                                self.MountTabCY1-(self.__MountTabWidth/2),
                                                0))
        tab = Part.makePlane(self.__MountTabLength+self.__WallThick,
                             self.__MountTabWidth,taborigin)\
                .extrude(Base.Vector(0,0,self.__WallThick))
        temp = Part.makePlane(self.__MountTabWidth/2,
                              self.__MountTabWidth,
                              taborigin).extrude(Base.Vector(0,0,self.__WallThick))
        rod = Part.makeCylinder(self.__MountTabWidth/2,
                                self.__WallThick,
                                taborigin.add(Base.Vector(self.__MountTabWidth/2,
                                                          self.__MountTabWidth/2,0)))
        #self.t = temp
        #self.r = rod
        tab = tab.cut(temp.cut(rod))

        hole = Part.makeCylinder(self.__MountTabHoleDiameter/2,
                                self.__WallThick,
                                taborigin.add(Base.Vector(self.__MountTabWidth/2,
                                                          self.__MountTabWidth/2,0)))
        tab = tab.cut(hole)
        bot = bot.fuse(tab)
        taborigin = self.origin.add(Base.Vector(-self.__MountTabLength,
                                                self.MountTabCY2-(self.__MountTabWidth/2),
                                                0))
        tab = Part.makePlane(self.__MountTabLength+self.__WallThick,
                             self.__MountTabWidth,taborigin)\
                .extrude(Base.Vector(0,0,self.__WallThick))
        temp = Part.makePlane(self.__MountTabWidth/2,
                              self.__MountTabWidth,
                              taborigin).extrude(Base.Vector(0,0,self.__WallThick))
        rod = Part.makeCylinder(self.__MountTabWidth/2,
                                self.__WallThick,
                                taborigin.add(Base.Vector(self.__MountTabWidth/2,
                                                          self.__MountTabWidth/2,0)))
        #self.t = temp
        #self.r = rod
        tab = tab.cut(temp.cut(rod))
        hole = Part.makeCylinder(self.__MountTabHoleDiameter/2,
                                self.__WallThick,
                                taborigin.add(Base.Vector(self.__MountTabWidth/2,
                                                          self.__MountTabWidth/2,0)))
        tab = tab.cut(hole)
        bot = bot.fuse(tab)
        taborigin = self.origin.add(Base.Vector(self.CaseWidth-self.__WallThick,
                                                self.MountTabCY1-(self.__MountTabWidth/2),
                                                0))
        tab = Part.makePlane(self.__MountTabLength+self.__WallThick,
                             self.__MountTabWidth,taborigin)\
                .extrude(Base.Vector(0,0,self.__WallThick))
        temp = Part.makePlane(self.__MountTabWidth/2,
                              self.__MountTabWidth,
                              taborigin.add(Base.Vector(
                                self.__MountTabLength+self.__WallThick-self.__MountTabWidth/2,0,0))
                              ).extrude(Base.Vector(0,0,self.__WallThick))
        rod = Part.makeCylinder(self.__MountTabWidth/2,
                                self.__WallThick,
                                taborigin.add(Base.Vector(self.__MountTabLength+self.__WallThick-self.__MountTabWidth/2,
                                                          self.__MountTabWidth/2,0)))
        #self.t = temp
        #self.r = rod
        tab = tab.cut(temp.cut(rod))
        hole = Part.makeCylinder(self.__MountTabHoleDiameter/2,
                                self.__WallThick,
                                taborigin.add(Base.Vector(self.__MountTabLength+self.__WallThick-self.__MountTabWidth/2,
                                                          self.__MountTabWidth/2,0)))
        tab = tab.cut(hole)
        bot = bot.fuse(tab)
        taborigin = self.origin.add(Base.Vector(self.CaseWidth-self.__WallThick,
                                                self.MountTabCY2-(self.__MountTabWidth/2),
                                                0))
        tab = Part.makePlane(self.__MountTabLength+self.__WallThick,
                             self.__MountTabWidth,taborigin)\
                .extrude(Base.Vector(0,0,self.__WallThick))
        temp = Part.makePlane(self.__MountTabWidth/2,
                              self.__MountTabWidth,
                              taborigin.add(Base.Vector(
                                self.__MountTabLength+self.__WallThick-self.__MountTabWidth/2,0,0))
                              ).extrude(Base.Vector(0,0,self.__WallThick))
        rod = Part.makeCylinder(self.__MountTabWidth/2,
                                self.__WallThick,
                                taborigin.add(Base.Vector(self.__MountTabLength+self.__WallThick-self.__MountTabWidth/2,
                                                          self.__MountTabWidth/2,0)))
        #self.t = temp
        #self.r = rod
        tab = tab.cut(temp.cut(rod))
        hole = Part.makeCylinder(self.__MountTabHoleDiameter/2,
                                self.__WallThick,
                                taborigin.add(Base.Vector(self.__MountTabLength+self.__WallThick-self.__MountTabWidth/2,
                                                          self.__MountTabWidth/2,0)))
        #self.r = hole
        tab = tab.cut(hole)
        bot = bot.fuse(tab)
        boardPostOrigin = self.origin.add(Base.Vector(self.__WallThick,
                                                      self.__WallThick,
                                                      0))
        for post in Board.HoleOffsets():
            pX, pY = post
            postOrig = boardPostOrigin.add(Base.Vector(pX,pY,0))
            post = Part.makeCylinder(self.__PostDiameter/2,
                                     self.PostLength,
                                     postOrig)
            post = post.fuse(
                Part.makeCylinder(self.__PostShoulderDiameter/2,
                                  self.PostShoulderLength,
                                  postOrig)
            )
            bot = bot.fuse(post)
            bot = bot.cut(
                Part.makeCylinder(self.__PostShoulderInnerDiameter/2,
                                  self.__PostShoulderDepth,
                                  postOrig)
            )               
            bot = bot.cut(
                Part.makeCylinder(self.__PostHoleDiameter/2,
                                  self.PostLength,
                                  postOrig)
            )
        return bot
    def __LEDRod(self,posXY):
        ledX, ledY = posXY
        #debug("*** __LEDRod(): ledX = %f, ledY = %f",ledX,ledY)
        #debug("*** __LEDRod(): self.origin = (%f, %f, %f)",self.origin.x,
        #                                                   self.origin.y,
        #                                                   self.origin.z)
        ledOrig = self.origin.add(Base.Vector(self.__WallThick+ledX,
                                              self.__WallThick+ledY,
                                              self.CaseBottomHeight+self.__LEDZOffset))
        #debug("*** __LEDRod(): ledOrig = (%f, %f, %f)",ledOrig.x,ledOrig.y,ledOrig.z)
        rodLength = self.CaseTopHeight-self.__WallThick/2
        return Part.makeCylinder(self.__LEDRodDiameter/2,rodLength,ledOrig)
    def __top(self):
        toporigin = self.origin.add(Base.Vector(0,0,self.CaseBottomHeight))
        top = Part.makePlane(self.CaseWidth,self.CaseLength,
                             toporigin.add(Base.Vector(0,0,self.CaseTopHeight-\
                                                           self.__WallThick*1.5))) \
            .extrude(Base.Vector(0,0,self.__WallThick))
        top = top.fuse(
            Part.makePlane(self.CaseTopHeight,self.CaseLength,
                           toporigin.add(Base.Vector(0,self.CaseLength,
                                                     -self.__WallThick/2)),
                           Base.Vector(1,0,0)).extrude(Base.Vector(self.__WallThick,0,0))
        )
        top = top.cut(
            Part.makePlane(self.__WallThick/2,
                               self.CaseLength-self.__WallThick,
                               toporigin.add(Base.Vector(self.__WallThick/2,
                                             self.CaseLength-self.__WallThick/2,
                                             -self.__WallThick/2)),
                               Base.Vector(1,0,0)).extrude(Base.Vector(self.__WallThick/2,0,0))
        )
        top = top.fuse(
            Part.makePlane(self.CaseTopHeight,self.CaseLength,
                           toporigin.add(Base.Vector(self.CaseWidth-self.__WallThick,
                                                     self.CaseLength,
                                                     -self.__WallThick/2)),
                           Base.Vector(1,0,0)).extrude(Base.Vector(self.__WallThick,0,0))
        )
        top = top.cut(
            Part.makePlane(self.__WallThick/2,
                               self.CaseLength-self.__WallThick,
                               toporigin.add(Base.Vector(self.CaseWidth-self.__WallThick,
                                             self.CaseLength-self.__WallThick/2,
                                             -self.__WallThick/2)),
                               Base.Vector(1,0,0)).extrude(Base.Vector(self.__WallThick/2,0,0))
        )
        top = top.fuse(
            Part.makePlane(self.CaseTopHeight,self.CaseWidth,
                           toporigin.add(Base.Vector(0,0,-self.__WallThick/2)),
                           Base.Vector(0,1,0)).extrude(Base.Vector(0,self.__WallThick,0))
        )
        top = top.cut(
            Part.makePlane(self.__WallThick/2,self.CaseWidth-self.__WallThick,
                           toporigin.add(Base.Vector(self.__WallThick/2,
                                                     self.__WallThick/2,
                                                     -self.__WallThick/2)),
                           Base.Vector(0,1,0)).extrude(Base.Vector(0,self.__WallThick,0))
                           
        )
        top = top.fuse(
            Part.makePlane(self.CaseTopHeight,self.CaseWidth,
                           toporigin.add(Base.Vector(0,self.CaseLength-self.__WallThick,-self.__WallThick/2)),
                           Base.Vector(0,1,0)).extrude(Base.Vector(0,self.__WallThick,0))
        )
        top = top.cut(
            Part.makePlane(self.__WallThick/2,self.CaseWidth-self.__WallThick,
                           toporigin.add(Base.Vector(self.__WallThick/2,
                                                     self.CaseLength-self.__WallThick*1.5,
                                                     -self.__WallThick/2)),
                           Base.Vector(0,1,0)).extrude(Base.Vector(0,self.__WallThick,0))        
        )
        temp = Part.makePlane(self.__WallThick,self.__WallThick,
                              toporigin.add(Base.Vector(0,0,self.CaseTopHeight-self.__WallThick*1.5)),
                              Base.Vector(0,1,0))\
                .extrude(Base.Vector(0,self.CaseLength,0))
        offset = Base.Vector(self.__WallThick,0,self.CaseTopHeight-self.__WallThick*1.5)
        rod = Part.makeCylinder(self.__WallThick,self.CaseLength,
                                toporigin.add(offset),Base.Vector(0,1,0))
        top = top.cut(temp.cut(rod))
        temp = Part.makePlane(self.__WallThick,self.__WallThick,
                              toporigin.add(Base.Vector(self.CaseWidth-self.__WallThick,
                                     0,self.CaseTopHeight-self.__WallThick*1.5)),
                              Base.Vector(0,1,0))\
                .extrude(Base.Vector(0,self.CaseLength,0))
        offset = Base.Vector(self.CaseWidth-self.__WallThick,0,self.CaseTopHeight-self.__WallThick*1.5)
        rod = Part.makeCylinder(self.__WallThick,self.CaseLength,
                                toporigin.add(offset),Base.Vector(0,1,0))
        top = top.cut(temp.cut(rod))
        temp = Part.makePlane(self.__WallThick,self.__WallThick,
                              toporigin.add(Base.Vector(0,self.__WallThick,
                                     self.CaseTopHeight-self.__WallThick*1.5)),
                              Base.Vector(1,0,0)).extrude(Base.Vector(self.CaseWidth,0,0))
        offset = Base.Vector(0,self.__WallThick,self.CaseTopHeight-self.__WallThick*1.5)
        rod = Part.makeCylinder(self.__WallThick,self.CaseWidth,
                                toporigin.add(offset),Base.Vector(1,0,0))
        top = top.cut(temp.cut(rod))
        temp = Part.makePlane(self.__WallThick,self.__WallThick,
                              toporigin.add(Base.Vector(0,self.CaseLength,
                                self.CaseTopHeight-self.__WallThick*1.5)),
                              Base.Vector(1,0,0)).extrude(Base.Vector(self.CaseWidth,0,0))
        offset = Base.Vector(0,self.CaseLength-self.__WallThick,
                             self.CaseTopHeight-self.__WallThick*1.5)
        rod = Part.makeCylinder(self.__WallThick,self.CaseWidth,
                                toporigin.add(offset),Base.Vector(1,0,0))
        top = top.cut(temp.cut(rod))
        temp = Part.makePlane(self.__WallThick,self.__WallThick,
                              toporigin.add(Base.Vector(0,0,-self.__WallThick/2)))\
                                .extrude(Base.Vector(0,0,self.CaseTopHeight))
        rod = Part.makeCylinder(self.__WallThick,self.CaseTopHeight,
                                toporigin.add(Base.Vector(self.__WallThick,
                                                          self.__WallThick,
                                                          -self.__WallThick/2)))
        top = top.cut(temp.cut(rod))
        temp = Part.makePlane(self.__WallThick,self.__WallThick,
                              toporigin.add(Base.Vector(0,self.CaseLength-self.__WallThick,-self.__WallThick/2))
                              ).extrude(Base.Vector(0,0,self.CaseTopHeight))
        rod = Part.makeCylinder(self.__WallThick,self.CaseTopHeight,
                                toporigin.add(Base.Vector(self.__WallThick,
                                                            self.CaseLength-self.__WallThick,-self.__WallThick/2)))
        self.t = temp
        self.r = rod
        top = top.cut(temp.cut(rod))
        temp = Part.makePlane(self.__WallThick,self.__WallThick,
                              toporigin.add(Base.Vector(self.CaseWidth-self.__WallThick,0,-self.__WallThick/2))
                              ).extrude(Base.Vector(0,0,self.CaseTopHeight))
        rod = Part.makeCylinder(self.__WallThick,self.CaseTopHeight,
                                toporigin.add(Base.Vector(self.CaseWidth-self.__WallThick,self.__WallThick,-self.__WallThick/2)))
        self.t = temp
        self.r = rod
        top = top.cut(temp.cut(rod))
        temp = Part.makePlane(self.__WallThick,self.__WallThick,
                              toporigin.add(Base.Vector(self.CaseWidth-self.__WallThick,
                                                          self.CaseLength-self.__WallThick,-self.__WallThick/2))
                              ).extrude(Base.Vector(0,0,self.CaseTopHeight))
        rod = Part.makeCylinder(self.__WallThick,self.CaseTopHeight,
                                toporigin.add(Base.Vector(self.CaseWidth-self.__WallThick,
                                                            self.CaseLength-self.__WallThick,-self.__WallThick/2)))
        top = top.cut(temp.cut(rod))

        
        bjopening = Part.makePlane(self.__BJHeight+self.__WallThick/2,
                                   self.__BJWidth,
                                   toporigin.add(Base.Vector(self.__BJXOffset+self.__WallThick,
                                                             self.CaseLength-self.__WallThick,
                                                             -self.__WallThick/2)),
                                   Base.Vector(0,1,0)).extrude(Base.Vector(0,self.__WallThick,0))
        #self.t = bjopening
        top = top.cut(bjopening)
        usbaopening = Part.makePlane(self.__USBAHeight+self.__WallThick/2,
                                     self.__USBAWidth,
                                     toporigin.add(Base.Vector(0,self.__USBAYOffset+self.__USBAWidth+self.__WallThick,-self.__WallThick/2)),
                                     Base.Vector(1,0,0))\
                 .extrude(Base.Vector(self.__WallThick,0,0))
        #self.t = usbaopening
        top = top.cut(usbaopening)
        lccpoutopening = Part.makePlane(self.__LCCPowerPlugHeight+self.__WallThick/2,
                                        self.__LCCPowerPlugWidth,
                                        toporigin.add(
                                            Base.Vector(self.__LCCPOutXOffset+self.__WallThick,
                                                        0,
                                                        -self.__WallThick/2)),
                                        Base.Vector(0,1,0))\
                        .extrude(Base.Vector(0,self.__WallThick,0))
        self.t = lccpoutopening
        top = top.cut(lccpoutopening)
        lccrj45sopening = Part.makePlane(self.__LCCRJ45Height+self.__WallThick/2,
                                         self.__LCCRJ45Width,
                                         toporigin.add(
                                            Base.Vector(self.__LCCRJ45XOffset+self.__WallThick,
                                                        0,
                                                        -self.__WallThick/2)),
                                         Base.Vector(0,1,0))\
                        .extrude(Base.Vector(0,self.__WallThick,0))
        self.t = lccrj45sopening
        top = top.cut(lccrj45sopening)
        lccpinopening = Part.makePlane(self.__LCCPowerPlugHeight+self.__WallThick/2,
                                        self.__LCCPowerPlugWidth,
                                        toporigin.add(
                                            Base.Vector(self.__LCCPInXOffset+self.__WallThick,
                                                        0,
                                                        -self.__WallThick/2)),
                                        Base.Vector(0,1,0))\
                        .extrude(Base.Vector(0,self.__WallThick,0))
        self.t = lccpinopening
        top = top.cut(lccpinopening)
        trackpoweropening = Part.makePlane(self.__TrackPowerHeight+self.__WallThick/2,
                                        self.__TrackPowerWidth,
                                        toporigin.add(
                                            Base.Vector(self.__TrackPowerXOffset+self.__WallThick,
                                                        0,
                                                        -self.__WallThick/2)),
                                        Base.Vector(0,1,0))\
                        .extrude(Base.Vector(0,self.__WallThick,0))
        self.t = trackpoweropening
        top = top.cut(trackpoweropening)
        self.lccTxAct = self.__LEDRod(self.__LCCTxAct)
        top = top.cut(self.lccTxAct)
        self.lccRxAct = self.__LEDRod(self.__LCCRxAct)
        top = top.cut(self.lccRxAct)
        self.opsBAct  = self.__LEDRod(self.__OPSBAct)
        top = top.cut(self.opsBAct)
        self.opsAAct  = self.__LEDRod(self.__OPSAAct)
        top = top.cut(self.opsAAct)
        self.progBAct  = self.__LEDRod(self.__ProgBAct)
        top = top.cut(self.progBAct)
        self.progAAct  = self.__LEDRod(self.__ProgAAct)
        top = top.cut(self.progAAct)
        self.power     = self.__LEDRod(self.__Power)
        top = top.cut(self.power)

        boardPostOrigin = toporigin.add(Base.Vector(self.__WallThick,         
                                                    self.__WallThick,
                                                    0))
        for post in Board.HoleOffsets():
            pX, pY = post
            postOrig = boardPostOrigin.add(Base.Vector(pX,pY,0))
            post = Part.makeCylinder(self.__PostDiameter/2,
                                     self.TopPostLength,
                                     postOrig)
            post = post.cut(
                Part.makeCylinder(self.__TopPostDrillDiameter/2,
                                  self.TopPostDrillDepth,
                                  postOrig)
            )
            top = top.fuse(post)
        for ventCol in range(0,10):
            ventY = self.__WallThick+5.2755+ventCol*10.5510
            for ventRow in range(0,2):
                ventZ = 8.4200+ventRow*8.4200
                hole = Part.makeCylinder(self.__VentHoleDiameter/2,
                                         self.__WallThick,
                                         toporigin.add(
                                            Base.Vector(
                                                self.CaseWidth-self.__WallThick,
                                                ventY,ventZ)),
                                         Base.Vector(1,0,0))
                top = top.cut(hole)
                if ventRow == 1 or \
                   ventY > (self.__USBAYOffset+self.__USBAWidth+self.__VentHoleDiameter) or \
                   ventY < (self.__USBAYOffset):
                    hole = Part.makeCylinder(self.__VentHoleDiameter/2,
                                             self.__WallThick,
                                             toporigin.add(
                                                Base.Vector(0,ventY,ventZ)),
                                             Base.Vector(1,0,0))
                    top = top.cut(hole)
        for ventCol in range(0,5):
            ventX = 2.5+(ventCol*5)
            for ventRow in range(0,5):
                if (ventCol == 0 or ventCol == 4) and \
                   (ventRow == 0 or ventRow == 4):
                    continue
                ventY = 2.5+(ventRow*5)
                hole = Part.makeCylinder(self.__VentHoleDiameter/2,
                                         self.__WallThick,
                                         toporigin.add(
                                            Base.Vector(
                                                self.__FANXOffset+self.__WallThick+ventX,
                                                self.__FANYOffset+self.__WallThick+ventY,
                                                self.CaseTopHeight-self.__WallThick*1.5)))
                top = top.cut(hole)
        displayOrigin = toporigin.add(Base.Vector(self.__DisplayXOffset,
                                                  self.__DisplayYOffset,
                                                  self.CaseTopHeight-self.__WallThick*1.5-1.6))
        self.display = Adafruit_91_128x32_STEAMMA(self.name+"_Adafruit_91_128x32_STEAMMA",displayOrigin)
        for ih in range(0,4):
            top = top.cut(
                self.display.MountHole(ih,
                                       toporigin.z+self.CaseTopHeight-self.__WallThick*1.5,
                                       self.__WallThick)
            )
        top = top.cut(
            self.display.ScreenCutout(toporigin.z+self.CaseTopHeight-self.__WallThick*1.5,
                                      self.__WallThick)
        )
        return top
    def __init__(self,name,origin=Base.Vector(0,0,0),fakeboard=True):
        self.name = name
        if not isinstance(origin,Base.Vector):
            raise RuntimeError("origin is not a Vector!")
        self.origin = origin
        self.bottom = self.__bottom()
        if fakeboard:
            self.board = Board(name+"_board",
                               self.origin.add(Base.Vector(self.__WallThick,
                                                           self.__WallThick,
                                                           self.CaseBottomHeight-self.__BoardThick)))
        else:
            self.board = None
        self.top = self.__top()
        self.bottom = self.bottom.cut(self.top)
    def show(self,doc=None):
        if doc==None:
            doc = App.activeDocument()
        obj = doc.addObject("Part::Feature",self.name+"_bottom")
        obj.Shape = self.bottom
        obj.Label=self.name+"_bottom"
        obj.ViewObject.ShapeColor=(0.5,0.5,0.5)
        if self.board != None:
            self.board.show(doc)
        obj = doc.addObject("Part::Feature",self.name+"_top")
        obj.Shape = self.top
        obj.Label=self.name+"_top"
        obj.ViewObject.ShapeColor=(0.5,0.5,0.5)
        obj = doc.addObject("Part::Feature",self.name+"_lccTxAct")
        obj.Shape = self.lccTxAct
        obj.Label=self.name+"_lccTxAct"
        obj.ViewObject.ShapeColor=(1.0,1.0,1.0)
        obj.ViewObject.Transparency=90
        obj = doc.addObject("Part::Feature",self.name+"_lccRxAct")
        obj.Shape = self.lccRxAct
        obj.Label=self.name+"_lccRxAct"
        obj.ViewObject.ShapeColor=(1.0,1.0,1.0)
        obj.ViewObject.Transparency=90
        obj = doc.addObject("Part::Feature",self.name+"_opsBAct")
        obj.Shape = self.opsBAct
        obj.Label=self.name+"_opsBAct"
        obj.ViewObject.ShapeColor=(1.0,1.0,1.0)
        obj.ViewObject.Transparency=90
        obj = doc.addObject("Part::Feature",self.name+"_opsAAct")
        obj.Shape = self.opsAAct
        obj.Label=self.name+"_opsAAct"
        obj.ViewObject.ShapeColor=(1.0,1.0,1.0)
        obj.ViewObject.Transparency=90
        obj = doc.addObject("Part::Feature",self.name+"_progBAct")
        obj.Shape = self.progBAct
        obj.Label=self.name+"_progBAct"
        obj.ViewObject.ShapeColor=(1.0,1.0,1.0)
        obj.ViewObject.Transparency=90
        obj = doc.addObject("Part::Feature",self.name+"_progAAct")
        obj.Shape = self.progAAct
        obj.Label=self.name+"_progAAct"
        obj.ViewObject.ShapeColor=(1.0,1.0,1.0)
        obj.ViewObject.Transparency=90
        obj = doc.addObject("Part::Feature",self.name+"_power")
        obj.Shape = self.power
        obj.Label=self.name+"_power"
        obj.ViewObject.ShapeColor=(1.0,1.0,1.0)
        obj.ViewObject.Transparency=90
        self.display.show(doc)
        #obj = doc.addObject("Part::Feature",self.name+"_r")
        #obj.Shape = self.r
        #obj.ViewObject.ShapeColor=(1.0,0.0,0.0)
        #obj = doc.addObject("Part::Feature",self.name+"_t")
        #obj.Shape = self.t
        #obj.ViewObject.ShapeColor=(0.0,1.0,0.0)
    def MakeSTL(self,basefilename="RevCBoardCase_"):
        doc = App.newDocument("TempDoc")
        obj = doc.addObject("Part::Feature","temp")
        obj.Shape=self.top.copy().rotate(Base.Vector(0,0,0),Base.Vector(1,0,0),180)
        objs = list()
        objs.append(obj)
        filename = basefilename+"Top.stl"
        Mesh.export(objs,filename)
        filename = basefilename+"Top.boundingbox"
        bb = self.top.BoundBox
        fp = open(filename,"w")
        fp.write("%10.6g,%10.6g,%10.6g\n"%(bb.XLength,bb.YLength,bb.ZLength))
        fp.close()
        doc.removeObject(obj.Label)
        obj = doc.addObject("Part::Feature","temp")
        obj.Shape=self.bottom
        objs = list()
        objs.append(obj)
        filename = basefilename+"Bottom.stl"
        Mesh.export(objs,filename)
        filename = basefilename+"Bottom.boundingbox"
        bb = self.bottom.BoundBox
        fp = open(filename,"w")
        fp.write("%10.6g,%10.6g,%10.6g\n"%(bb.XLength,bb.YLength,bb.ZLength))
        fp.close()
        doc.removeObject(obj.Label)
        App.closeDocument("TempDoc")
                
        
        
if __name__ == '__main__':
    #if "RevCBoardCase" in App.listDocuments().keys():
    #    App.closeDocument("RevCBoardCase")
    #doc = App.newDocument("RevCBoardCase")
    Gui.open(os.path.join(os.path.dirname(__file__),"PocketBeagleCommandStation_SMD.wrl"))
    doc = App.activeDocument()
    boardW, BoardH = Board.BoardSize()
    case = Case("case",Base.Vector(82.55,-166.45,-Case.ZOffset()),False)
    case.show(doc)
    Gui.activeDocument().activeView().viewFront()
    Gui.SendMsgToActiveView("ViewFit")
    case.MakeSTL()
